-- Small ASN.1 spec for tstodr test
test_odrcodec
{test_odrcodec} DEFINITIONS ::=
BEGIN
MySequence ::= SEQUENCE {
	first [1] IMPLICIT INTEGER,
	second [2] IMPLICIT OCTET STRING,
        third [3] IMPLICIT BOOLEAN,
        fourth [4] IMPLICIT NULL,
        fifth [5] IMPLICIT INTEGER {
                enum1(0),
                enum2(1)
        },
	myoid [6] IMPLICIT OBJECT IDENTIFIER
}
END
