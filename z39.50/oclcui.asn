UserInfoFormat-oclcUserInformation
{Z39-50-userInfoFormat OCLCUserInformation (7)} DEFINITIONS ::=
BEGIN

-- $Id: oclcui.asn,v 1.4 2003-09-04 17:44:49 adam Exp $
--
-- This format is returned from the server at
--	fsz3950test.oclc.org:210
-- I found the definition at
--	http://www.oclc.org/firstsearch/documentation/z3950/config_guide.htm
--
-- I have added OPTIONAL modifiers to the `dblist' and and `code'
-- elements because they appear to be admitted from the APDU returned
-- as an Init diagnostic from fsz3950test.oclc.org:210.  Adam further
-- removed the SEQUENCE structure, changed failReason to a BOOLEAN and
-- deleted diagnosticSetId altogether, to make the ASN.1 conform to
-- what's actually returned on the wire.  Finally, I removed the
-- OPTIONAL on failReason on the advice of OCLC's Keith Neibarger
-- <neibarge@oclc.org> (although he'd also advised me, wrongly, that I
-- could remove the OPTIONAL on dblist).

OCLC-UserInformation ::= SEQUENCE {
    motd        [1] IMPLICIT VisibleString OPTIONAL,
    dblist      SEQUENCE OF DBName OPTIONAL,
    failReason  [3] IMPLICIT BOOLEAN OPTIONAL,
    code        [1] IMPLICIT INTEGER OPTIONAL,
    text        [2] IMPLICIT VisibleString OPTIONAL
}

DBName ::= [2] IMPLICIT VisibleString

END
